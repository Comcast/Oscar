DOCS-TEST-MIB DEFINITIONS ::= BEGIN

IMPORTS
    MODULE-IDENTITY,
    OBJECT-TYPE,
    Integer32
                FROM SNMPv2-SMI
    TEXTUAL-CONVENTION,
    TruthValue
                FROM SNMPv2-TC
    OBJECT-GROUP,
    MODULE-COMPLIANCE
                FROM SNMPv2-CONF
    clabProjDocsis
                FROM CLAB-DEF-MIB;

docsTestMIB MODULE-IDENTITY
    LAST-UPDATED    "200708290000Z" -- August 29, 2007
    ORGANIZATION "Cable Television Laboratories, Inc."
    CONTACT-INFO
            "Postal: Cable Television Laboratories
                     858 Coal Creek Circle
                     Louisville, Colorado 80027-9750
                     U.S.A.
            Phone:   +1 303-661-9100
            Fax:     +1 303-661-9199
            E-mail:  mibs@cablelabs.com"
    DESCRIPTION
            "This MIB module contains the management objects for
            supporting programmable test features for DOCSIS
            compliant Cable Modems (CM) and Cable Modem 
            Termination Systems (CMTS).
            Copyright 1999-2007 Cable Television Laboratories, Inc.
            All rights reserved."
    REVISION "200708290000Z" -- August 29, 2007
    DESCRIPTION
            "This revision published as CM-SP-TestMIB-D04."
    REVISION "200702070000Z" -- February 7, 2007
    DESCRIPTION
            "This revision published as CM-SP-TestMIB-D03."
    REVISION "200203150000Z" -- March 15, 2002
    DESCRIPTION
            "This revision published as SP-TestMIBv2.0-D02."
            
    ::= { clabProjDocsis 12 }

-- Textual Conventions

--
-- Group definitions
--
docsTestMibObjects   OBJECT IDENTIFIER ::= { docsTestMIB 1 }
docsTestBaseObjects  OBJECT IDENTIFIER ::= { docsTestMibObjects 1 }
docsTestSetupObjects OBJECT IDENTIFIER ::= { docsTestMibObjects 2 }

--
-- docsTestBaseObjects
--
-- These objects indicate the capability and current status of the
-- programmable test features on the CM/CMTS.
--

docsTestCapability OBJECT-TYPE
    SYNTAX      OCTET STRING
    MAX-ACCESS  read-only
    STATUS      current
    DESCRIPTION
            "Indicates the ability of this device to support the 
            programmable features identified by the TYPE field from
            the CM/CMTS TLV Table.
            Each octet within this octet string represents eight tests.
            For example, the first octet represents tests one through 
            eight (with the msb representing test one) as identified
            by the TYPE field."
    REFERENCE
            "DOCSIS Testing MIB Specification CM-SP-TestMIB-D04-070829,
            Enumerated Test Modes Annex."
    ::= { docsTestBaseObjects 1 }

docsTestStatus OBJECT-TYPE
    SYNTAX      OCTET STRING
    MAX-ACCESS  read-only
    STATUS      current
    DESCRIPTION
            "Indicates the current operating status of tests initiated
            through the docsTestSetupObjects. The octet representation
            is identical to that used by docsTestCapability. A bit 
            representation of one indicates that a test is currently
            active, while zero indicates the test is inactive or has
            completed."
    ::= { docsTestBaseObjects 2 }

--
-- docsTestSetupObjects
--
-- These objects set up the test parameters and initiate the test.
--

docsTestType OBJECT-TYPE
    SYNTAX      Integer32 (0..1023)
    MAX-ACCESS  read-write
    STATUS      current
    DESCRIPTION
            "Corresponds to the TYPE field from the CM/CMTS TLV Table.
            The default value of zero indicates no test has yet been
            initiated. A 'wrongValue' error should be returned in
            response to a write request for a test not supported by
            the device. A read request will return the docsTestType
            value last successfully written, whether that test is
            active or inactive."
    REFERENCE
            "DOCSIS Testing MIB Specification CM-SP-TestMIB-D04-070829,
            Enumerated Test Modes Annex."
    DEFVAL { 0 }
    ::= { docsTestSetupObjects 1 }

docsTestData OBJECT-TYPE
    SYNTAX      OCTET STRING
    MAX-ACCESS  read-write
    STATUS      current
    DESCRIPTION
            "The OCTET STRING length and value correspond to the 
            LENGTH and VALUE fields from the CM/CMTS TLV Table. A read
            request will return the docsTestData value last
            successfully written, whether that test is active
            or inactive."
    REFERENCE
            "DOCSIS Testing MIB Specification CM-SP-TestMIB-D04-070829,
            Enumerated Test Modes Annex."
    ::= { docsTestSetupObjects 2 }

docsTestEnable OBJECT-TYPE
    SYNTAX      TruthValue
    MAX-ACCESS  read-write
    STATUS      current
    DESCRIPTION
            "Used to initiate or stop the tests setup through the
            docsTestType and docsTestData objects. A 'commitFailed'
            error should be returned in response to a 'true' write
            request if the values in docsTestType and docsTestData are
            incompatible, or a test could not be initiated for any
            other reason."
    ::= { docsTestSetupObjects 3 }

--
-- Compliance statements
--

docsTestConformance  OBJECT IDENTIFIER    ::= { docsTestMIB 2 }
docsTestCompliances  OBJECT IDENTIFIER    ::= { docsTestConformance 1 }
docsTestGroups       OBJECT IDENTIFIER    ::= { docsTestConformance 2 }

docsTestBasicCompliance MODULE-COMPLIANCE
    STATUS      current
    DESCRIPTION
            "The compliance statement for devices that implement
            the DOCSIS compliant programmable test features."

MODULE  -- docsTestMib

-- unconditionally mandatory groups
MANDATORY-GROUPS {
        docsTestGroup
        }
    ::= { docsTestCompliances 1 }


docsTestGroup OBJECT-GROUP
    OBJECTS {
            docsTestCapability,
            docsTestStatus,
            docsTestType,
            docsTestData,
            docsTestEnable
    }
    STATUS      current
    DESCRIPTION
            "Group of objects implemented in both Cable Modems and
            Cable Modem Termination Systems."
    ::= { docsTestGroups 1 }

END
