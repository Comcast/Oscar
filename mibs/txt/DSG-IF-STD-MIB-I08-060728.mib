DSG-IF-STD-MIB DEFINITIONS ::= BEGIN
IMPORTS
    MODULE-IDENTITY,
    OBJECT-TYPE, 
    NOTIFICATION-TYPE,
    Integer32,
    Unsigned32, 
    Counter32                FROM SNMPv2-SMI         --RFC 2578

    OBJECT-GROUP,
    NOTIFICATION-GROUP,
    MODULE-COMPLIANCE        FROM SNMPv2-CONF        -- RFC 2580

    MacAddress               FROM SNMPv2-TC          -- RFC 2579

    InetAddressType, 
    InetAddress,
    InetAddressPrefixLength,
    InetPortNumber           FROM INET-ADDRESS-MIB   -- RFC 3291

    ifPhysAddress            FROM IF-MIB             -- RFC 2863

    docsDevEvLevel,
    docsDevEvId,
    docsDevEvText            FROM DOCS-CABLE-DEVICE-MIB   --RFC 2669

    docsIfCmCmtsAddress,
    docsIfDocsisBaseCapability,
    docsIfCmStatusDocsisOperMode,
    docsIfCmStatusModulationType
                             FROM DOCS-IF-MIB  -- RFI MIB v2.0 draft 05

    clabProjDocsis           FROM CLAB-DEF-MIB;

dsgIfStdMib MODULE-IDENTITY
    LAST-UPDATED "200607280000Z" -- July 28, 2006
    ORGANIZATION "CableLabs DSG Working Group"
    CONTACT-INFO 
             "Postal: Cable Television Laboratories, Inc. 
                     858 Coal Creek Circle 
                     Louisville, Colorado 80027
                     U.S.A. 
             Phone : +1 303-661-9100 
             Fax   : +1 303-661-9199 
             E-mail: mibs@cablelabs.com "
    DESCRIPTION
            "This MIB module provides the management objects of 
            the DOCSIS Set-top Gateway (DSG) client controller 
            CM component for DSG operations of Set-top devices."
    REVISION    "200607280000Z" -- July 28, 2006
    DESCRIPTION
            "This revision is published as part of the CableLabs
            DSG specification.

            Copyright 1999-2006 Cable Television Laboratories, Inc.
            All rights reserved."
    ::= { clabProjDocsis 4 }

-----------------------------------------------------------------------
--
-- DSG eCM MIB objects that represent the DSG Configuration parameters
-- Tunnels information and list of available downstream channels
--  carrying the Set-top box content.
--
------------------------------------------------------------------------

dsgIfStdNotifications     OBJECT IDENTIFIER ::= { dsgIfStdMib 0 }
dsgIfStdMibObjects        OBJECT IDENTIFIER ::= { dsgIfStdMib 1 }
dsgIfStdConfig            OBJECT IDENTIFIER ::= { dsgIfStdMibObjects 1 }
dsgIfStdTunnelFilter      OBJECT IDENTIFIER ::= { dsgIfStdMibObjects 2 }
dsgIfStdDsgChannelList    OBJECT IDENTIFIER ::= { dsgIfStdMibObjects 3 }

------------------------------------------------------------------------
-- DSG eCM Scalar objects
------------------------------------------------------------------------

dsgIfStdDsgMode OBJECT-TYPE
    SYNTAX      INTEGER {
                basic(1),
                advanced(2)
                }
    MAX-ACCESS  read-only 
    STATUS      current 
    DESCRIPTION 
            "The DSG Mode of operation of this device." 
    ::= { dsgIfStdConfig 1 }

dsgIfStdTdsg1 OBJECT-TYPE
    SYNTAX      Unsigned32
    UNITS       "seconds"
    MAX-ACCESS  read-only
    STATUS      current
    DESCRIPTION
            "The configured value for the Tdsg1 timer."
    DEFVAL { 2 }
    ::= { dsgIfStdConfig 2 }

dsgIfStdTdsg2 OBJECT-TYPE
    SYNTAX      Unsigned32
    UNITS       "seconds"
    MAX-ACCESS  read-only
    STATUS      current
    DESCRIPTION
            "The configured value for the Tdsg2 timer."
    DEFVAL { 600 }
    ::= { dsgIfStdConfig 3 }

dsgIfStdTdsg3 OBJECT-TYPE
    SYNTAX      Unsigned32
    UNITS       "seconds"
    MAX-ACCESS  read-only
    STATUS      current
    DESCRIPTION
            "The configured value for the Tdsg3 timer."
    DEFVAL { 300 } 
    ::= { dsgIfStdConfig 4 }

dsgIfStdTdsg4 OBJECT-TYPE
    SYNTAX      Unsigned32
    UNITS       "seconds"
    MAX-ACCESS  read-only
    STATUS      current
    DESCRIPTION
            "The configured value for the Tdsg4 timer."
    DEFVAL { 1800 }
    ::= { dsgIfStdConfig 5 }

dsgIfStdTdsg1Timeouts OBJECT-TYPE
    SYNTAX      Counter32
    MAX-ACCESS  read-only
    STATUS      current
    DESCRIPTION
            "The number of times Tdsg1 expired in the DSG eCM since 
            last reboot."
    ::= { dsgIfStdConfig 6 }
    
dsgIfStdTdsg2Timeouts OBJECT-TYPE
    SYNTAX      Counter32
    MAX-ACCESS  read-only
    STATUS      current
    DESCRIPTION
            "The number of times Tdsg2 expired in the DSG eCM since
            last reboot."
    ::= { dsgIfStdConfig 7 }

dsgIfStdTdsg3Timeouts OBJECT-TYPE
    SYNTAX      Counter32
    MAX-ACCESS  read-only
    STATUS      current
    DESCRIPTION
            "The number of times Tdsg3 expired in the DSG eCM since
            last reboot."
    ::= { dsgIfStdConfig 8 }

dsgIfStdTdsg4Timeouts OBJECT-TYPE
    SYNTAX      Counter32
    MAX-ACCESS  read-only
    STATUS      current
    DESCRIPTION
            "The number of times Tdsg4 expired in the DSG eCM since
            last reboot."
    ::= { dsgIfStdConfig 9 }

------------------------------------------------------------------------
-- Active Tunnel filters, one row per Tunnel classifier 
-- (or tunnel for those that don't have classifiers)
------------------------------------------------------------------------

dsgIfStdTunnelFilterTable OBJECT-TYPE 
    SYNTAX      SEQUENCE OF DsgIfStdTunnelFilterEntry 
    MAX-ACCESS  not-accessible 
    STATUS      current
    DESCRIPTION
            "A Table with the DSG tunnels the DSG eCM is filtering 
            and forwarding to the DSG Clients." 
    ::= { dsgIfStdTunnelFilter 1 } 

dsgIfStdTunnelFilterEntry OBJECT-TYPE 
    SYNTAX      DsgIfStdTunnelFilterEntry 
    MAX-ACCESS  not-accessible 
    STATUS      current 
    DESCRIPTION 
            "The DSG eCM will have one entry for each DSG Tunnel
            Filter. A DSG eCM in Advanced mode will have at least one
            such Filter for each DSG classifier, and at least one such
            Filter for each DSG Tunnel that lacks a DSG classifier
            (i.e., the DSG Tunnel MAC address is the only relevant
            filtering parameter). The DSG eCM in Basic mode will have at
            least one entry for each DSG Tunnel MAC Address. Entries
            are created when the eCM is instructed to begin forwarding
            particular DSG Tunnels by the DSG Client Controller. 
            Entries are deleted when the eCM is no longer instructed to
            forward those particular DSG Tunnels by the DSG Client 
            Controller."
    INDEX { dsgIfStdTunnelFilterIndex }
    ::= { dsgIfStdTunnelFilterTable 1 }

DsgIfStdTunnelFilterEntry ::=  SEQUENCE {
    dsgIfStdTunnelFilterIndex              Unsigned32,
    dsgIfStdTunnelFilterApplicationId      Integer32,
    dsgIfStdTunnelFilterMacAddress         MacAddress,
    dsgIfStdTunnelFilterIpAddressType      InetAddressType,
    dsgIfStdTunnelFilterSrcIpAddr          InetAddress,
    dsgIfStdTunnelFilterSrcIpMask          InetAddress,
    dsgIfStdTunnelFilterDestIpAddr         InetAddress,
    dsgIfStdTunnelFilterDestPortStart      InetPortNumber,
    dsgIfStdTunnelFilterDestPortEnd        InetPortNumber,
    dsgIfStdTunnelFilterPkts               Counter32,
    dsgIfStdTunnelFilterOctets             Counter32,
    dsgIfStdTunnelFilterTimeActive         Counter32,
    dsgIfStdTunnelFilterTunnelId           Unsigned32
    }

dsgIfStdTunnelFilterIndex OBJECT-TYPE
    SYNTAX      Unsigned32 
    MAX-ACCESS  not-accessible
    STATUS      current 
    DESCRIPTION 
            "The unique index of entries in this table." 
    ::= { dsgIfStdTunnelFilterEntry 1 }

dsgIfStdTunnelFilterApplicationId OBJECT-TYPE
    SYNTAX      Integer32 (-1 | 0.. 65535)
    MAX-ACCESS  read-only
    STATUS      current 
    DESCRIPTION 
            "The ID of the application to which this DSG Tunnel is to
            be forwarded. This object returns -1 for: DSG Tunnels that
            do not have an associated Application ID or for DSG Tunnels
            for which the Application ID is unknown. In an OpenCable
            Host, this object returns '0' for a DSG Tunnel whose client
            resides on the Card." 
    DEFVAL { -1 }
    ::= { dsgIfStdTunnelFilterEntry 2 }

dsgIfStdTunnelFilterMacAddress OBJECT-TYPE
    SYNTAX      MacAddress
    MAX-ACCESS  read-only
    STATUS      current 
    DESCRIPTION 
            "The destination MAC Address associated with this 
            tunnel entry." 
    ::= { dsgIfStdTunnelFilterEntry 3 }

dsgIfStdTunnelFilterIpAddressType OBJECT-TYPE
    SYNTAX      InetAddressType 
    MAX-ACCESS  read-only
    STATUS      current 
    DESCRIPTION 
            "The type of InetAddress for dsgIfStdTunnelFilterSrcIpAddr,
            dsgIfStdTunnelFilterSrcIpMask and 
            dsgIfStdTunnelFilterDestIpAddr." 
    ::= { dsgIfStdTunnelFilterEntry 4 }

dsgIfStdTunnelFilterSrcIpAddr OBJECT-TYPE
    SYNTAX      InetAddress
    MAX-ACCESS  read-only
    STATUS      current 
    DESCRIPTION 
            "The source IP Address associated to this tunnel for the
            DSG eCM filtering and forwarding process. A value of zero
            indicates that source IP Address filtering does not apply.
            The type of this address is determined by the value of the
            dsgIfStdTunnelFilterIpAddressType object."
    DEFVAL { '00000000'h }
    ::= { dsgIfStdTunnelFilterEntry 5 }

dsgIfStdTunnelFilterSrcIpMask OBJECT-TYPE
    SYNTAX      InetAddress
    MAX-ACCESS  read-only
    STATUS      current 
    DESCRIPTION 
            "The Source IP Mask to be used along with 
            dsgIfStdTunnelFilterSrcIpAddr for filtering
            and forwarding of DSG Tunnel traffic.
            The type of this address is determined by the value of the
            dsgIfStdTunnelFilterIpAddressType object."
    DEFVAL { 'FFFFFFFF'h }
    ::= { dsgIfStdTunnelFilterEntry 6 }

dsgIfStdTunnelFilterDestIpAddr OBJECT-TYPE
    SYNTAX      InetAddress
    MAX-ACCESS  read-only
    STATUS      current 
    DESCRIPTION 
            "The destination IP Address associated to this tunnel for 
            the DSG eCM filtering and forwarding process. A value of
            zero indicates that destination IP Address filtering does
            not apply. The type of this address is determined by the
            value of the dsgIfStdTunnelFilterIpAddressType object."
    DEFVAL { '00000000'h }
    ::= { dsgIfStdTunnelFilterEntry 7 }

dsgIfStdTunnelFilterDestPortStart OBJECT-TYPE
    SYNTAX      InetPortNumber
    MAX-ACCESS  read-only
    STATUS      current 
    DESCRIPTION 
            "The lower UDP port value to be matched for this tunnel."
    DEFVAL { 0 } 
    ::= { dsgIfStdTunnelFilterEntry 8 }

dsgIfStdTunnelFilterDestPortEnd OBJECT-TYPE
    SYNTAX      InetPortNumber
    MAX-ACCESS  read-only
    STATUS      current 
    DESCRIPTION 
            "The upper UDP port value to be matched for this tunnel."
    DEFVAL { 65535 } 
    ::= { dsgIfStdTunnelFilterEntry 9 }

dsgIfStdTunnelFilterPkts OBJECT-TYPE
    SYNTAX      Counter32
    UNITS       "packets"
    MAX-ACCESS  read-only
    STATUS      current 
    DESCRIPTION 
            "The total number of Packets being classified and filtered 
            for this tunnel entry since creation of the entry."
    ::= { dsgIfStdTunnelFilterEntry 10 }

dsgIfStdTunnelFilterOctets OBJECT-TYPE
    SYNTAX      Counter32
    UNITS       "octets" 
    MAX-ACCESS  read-only
    STATUS      current 
    DESCRIPTION 
            "The total number of octets being classified and filtered 
            for this tunnel entry since creation of the entry." 
    ::= { dsgIfStdTunnelFilterEntry 11 }

dsgIfStdTunnelFilterTimeActive OBJECT-TYPE
    SYNTAX      Counter32
    UNITS       "seconds"
    MAX-ACCESS  read-only
    STATUS      current 
    DESCRIPTION 
            "The total number of seconds that this tunnel entry has
            been instantiated." 
    ::= { dsgIfStdTunnelFilterEntry 12 }

dsgIfStdTunnelFilterTunnelId OBJECT-TYPE
    SYNTAX      Unsigned32 (0 | 1..255)
    MAX-ACCESS  read-only
    STATUS      current 
    DESCRIPTION 
            "In DSG Advanced Mode, this is the tunnel identifier passed
            to the DSG eCM by the DSG-Client Controller for this Tunnel
            Filter entry. This value may correspond to the DSG Rule ID
            from the DCD message. In DSG Basic mode this object returns
            zero."
    DEFVAL { 0 }
    ::= { dsgIfStdTunnelFilterEntry 13 }

------------------------------------------------------------------------
-- DSG Channel List Table, one row per DSG Channel Frequency provided
-- in the DCD message.
------------------------------------------------------------------------

dsgIfStdDsgChannelListTable OBJECT-TYPE 
    SYNTAX      SEQUENCE OF DsgIfStdDsgChannelListEntry 
    MAX-ACCESS  not-accessible 
    STATUS      current
    DESCRIPTION
            "This table contains the list of DSG channels provided to
            the DSG eCM for use in scanning."
    ::= { dsgIfStdDsgChannelList 1 } 

dsgIfStdDsgChannelListEntry OBJECT-TYPE 
    SYNTAX      DsgIfStdDsgChannelListEntry 
    MAX-ACCESS  not-accessible 
    STATUS      current 
    DESCRIPTION 
            "The conceptual row for this table. The DSG eCM
             creates an entry per each downstream channel provided in 
             the DCD message. An entry is deleted when removed from the
             DCD message."
    INDEX { dsgIfStdDsgChannelListIndex }
    ::= { dsgIfStdDsgChannelListTable 1 }

DsgIfStdDsgChannelListEntry ::=  SEQUENCE {
    dsgIfStdDsgChannelListIndex      Unsigned32,
    dsgIfStdDsgChannelListFrequency  Unsigned32
    }

dsgIfStdDsgChannelListIndex OBJECT-TYPE
    SYNTAX      Unsigned32
    MAX-ACCESS  not-accessible
    STATUS      current 
    DESCRIPTION 
            "The unique identifier for entries in this table" 
    ::= { dsgIfStdDsgChannelListEntry 1 }

dsgIfStdDsgChannelListFrequency OBJECT-TYPE
    SYNTAX      Unsigned32
    UNITS       "Hertz"
    MAX-ACCESS  read-only
    STATUS      current 
    DESCRIPTION 
            "The downstream channel center frequency of this entry."
    ::= { dsgIfStdDsgChannelListEntry 2 }

--
-- Notification Definitions
--

dsgIfStdUpstreamEnabledNotify NOTIFICATION-TYPE
    OBJECTS {
            docsDevEvLevel,
            docsDevEvId,
            docsDevEvText,
            ifPhysAddress,
            docsIfCmCmtsAddress,
            docsIfDocsisBaseCapability,
            docsIfCmStatusDocsisOperMode,
            docsIfCmStatusModulationType
           }
    STATUS      current
    DESCRIPTION
            "Indicates the eCM is being instructed to have the upstream
            transmitter enabled. This notification is send after CM 
            registration.
            Note that the objects docsIfDocsisBaseCapability, 
            docsIfCmStatusDocsisOperMode and
            docsIfCmStatusModulationType may not be supported in some
            situations (e.g., for 1.1 CMs in 1.0 mode these objects are
            optional). If that is the case, the above varbind objects
            are indicated as noSuchName or noSuchObject for 
            SNMPv1 and SNMPv2 notification PDUs respectively."
    ::= { dsgIfStdNotifications 1 }

dsgIfStdUpstreamDisabledNotify NOTIFICATION-TYPE
    OBJECTS {
            docsDevEvLevel,
            docsDevEvId,
            docsDevEvText,
            ifPhysAddress,
            docsIfCmCmtsAddress,
            docsIfDocsisBaseCapability,
            docsIfCmStatusDocsisOperMode,
            docsIfCmStatusModulationType
           }
    STATUS      current
    DESCRIPTION
            "Indicates the CM is being instructed to have the upstream
            transmitter disabled. This notification is only send when 
            the CM is registered and prior to disable the upstream
            transmitter. Note that the objects
            docsIfDocsisBaseCapability, docsIfCmStatusDocsisOperMode
            and docsIfCmStatusModulationType may not be supported in
            some situations (e.g., for 1.1 CMs in 1.0 mode these objects
            are optional). If that is the case the above varbind
            objects are indicated as noSuchName or noSuchObject for 
            SNMPv1 and SNMPv2 notification PDUs respectively."
    ::= { dsgIfStdNotifications 2 }

dsgIfStdTdsg2TimeoutNotify NOTIFICATION-TYPE
    OBJECTS {
            docsDevEvLevel,
            docsDevEvId,
            docsDevEvText,
            ifPhysAddress,
            docsIfCmCmtsAddress,
            docsIfDocsisBaseCapability,
            docsIfCmStatusDocsisOperMode,
            docsIfCmStatusModulationType
           }
    STATUS      current
    DESCRIPTION
            "Notifies that the eCM has a timeout Tdsg2. 
            Note that the objects docsIfDocsisBaseCapability, 
            docsIfCmStatusDocsisOperMode and 
            docsIfCmStatusModulationType may not be supported is some
            situations (e.g., for 1.1 CMs in 1.0 mode these objects are
            optional). If that is the case the above varbind objects
            are indicated as noSuchName or noSuchObject for 
            SNMPv1 and SNMPv2 notification PDUs respectively."
    ::= { dsgIfStdNotifications 3 }

-- 
-- Conformance definitions 
-- 
dsgIfStdConformance  OBJECT IDENTIFIER ::= { dsgIfStdMib 2 } 
dsgIfStdCompliances  OBJECT IDENTIFIER ::= { dsgIfStdConformance 1 } 
dsgIfStdGroups       OBJECT IDENTIFIER ::= { dsgIfStdConformance 2 } 


dsgIfStdBasicCompliance MODULE-COMPLIANCE 
    STATUS      current 
    DESCRIPTION 
            "The compliance statement for DOCSIS Set-top Gateway eCMs."

MODULE -- dsgIfStdMIB

 -- mandatory groups

MANDATORY-GROUPS {
                 dsgIfStdConfigGroup,
                 dsgIfStdNotifyGroup 
                 }
    ::= { dsgIfStdCompliances 1 }


dsgIfStdConfigGroup OBJECT-GROUP
    OBJECTS {
            dsgIfStdDsgMode,
            dsgIfStdTdsg1,
            dsgIfStdTdsg2,
            dsgIfStdTdsg3,
            dsgIfStdTdsg4,
            dsgIfStdTdsg1Timeouts,
            dsgIfStdTdsg2Timeouts,
            dsgIfStdTdsg3Timeouts,
            dsgIfStdTdsg4Timeouts,
            dsgIfStdTunnelFilterApplicationId,
            dsgIfStdTunnelFilterMacAddress,
            dsgIfStdTunnelFilterIpAddressType,
            dsgIfStdTunnelFilterSrcIpAddr,
            dsgIfStdTunnelFilterSrcIpMask,
            dsgIfStdTunnelFilterDestIpAddr,
            dsgIfStdTunnelFilterDestPortStart,
            dsgIfStdTunnelFilterDestPortEnd,
            dsgIfStdTunnelFilterPkts,
            dsgIfStdTunnelFilterOctets,
            dsgIfStdTunnelFilterTimeActive,
            dsgIfStdTunnelFilterTunnelId,
            dsgIfStdDsgChannelListFrequency
            }
    STATUS      current
    DESCRIPTION
            "A collection of configuration elements provided in DCD 
            messages and DSG operations."
    ::= { dsgIfStdGroups 1 } 

dsgIfStdNotifyGroup NOTIFICATION-GROUP
    NOTIFICATIONS { dsgIfStdUpstreamEnabledNotify, 
                  dsgIfStdUpstreamDisabledNotify,
                  dsgIfStdTdsg2TimeoutNotify
                  }
    STATUS      current
    DESCRIPTION
            "The collection of DSG notifications that the eCM reports
             as part of the Set-top device"
    ::= { dsgIfStdGroups 2 }
END
