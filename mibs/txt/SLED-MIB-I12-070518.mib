SLED-MIB DEFINITIONS ::= BEGIN
IMPORTS
    MODULE-IDENTITY,
       Integer32,
       OBJECT-TYPE        FROM SNMPv2-SMI
       TruthValue,
       TimeStamp          FROM SNMPv2-TC
       OBJECT-GROUP,
       MODULE-COMPLIANCE  FROM SNMPv2-CONF 
    clabProjDocsis        FROM CLAB-DEF-MIB
    InterfaceIndex        FROM IF-MIB
    ;
    
sledMib MODULE-IDENTITY
    LAST-UPDATED       "200705180000Z" -- May 18, 2007
    ORGANIZATION       "CableLabs eDOCSIS Working Group"
    CONTACT-INFO 
            "Postal:   Cable Television Laboratories, Inc 
                       858 Coal Creek Circle
                       Louisville, CO 80027
                       U.S.A.
            Phone:  +1 303-661-9100
            Fax:    +1 303-661-9199
            E-mail: mibs@cablelabs.com"
    DESCRIPTION
            "This MIB module provides the management objects necessary
            to configure and invoke the Software Loopback Application 
            for eDOCSIS (SLED) functionality.

            Copyright 1999-2007 Cable Television Laboratories, Inc.
            All rights reserved."

    REVISION "200705180000Z" -- May 18, 2007
    DESCRIPTION
            "This revision is published as part of the CableLabs
            eDOCSIS Specification I12."

    REVISION "200607280000Z" -- July 28, 2006
    DESCRIPTION
            "This revision is published as part of the CableLabs
            eDOCSIS Specification I09."

    REVISION "200502090000Z" -- February 9, 2005
    DESCRIPTION
            "This revision is published as part of the CableLabs
            eDOCSIS Specification I05."
           
    REVISION "200411240000Z" -- November 24, 2004
    DESCRIPTION
            "This revision is published as part of the CableLabs
            eDOCSIS Specification I04."
           
    REVISION "200310150000Z" -- October 15, 2003
    DESCRIPTION
            "Initial version of the eDOCSIS SLED MIB module.
            This revision is published as part of the CableLabs
            eDOCSIS Specification I02."
           
    ::=  { clabProjDocsis 13 } 

-- Administrative assignments
sledNotifications             OBJECT IDENTIFIER ::= { sledMib 0 }
sledMibObjects                OBJECT IDENTIFIER ::= { sledMib 1 }
sledMibNotificationsObjects   OBJECT IDENTIFIER ::= { sledMib 2 }
sledMibConformance            OBJECT IDENTIFIER ::= { sledMib 3 }

-- Object Groups
sledGlobal        OBJECT IDENTIFIER ::= { sledMibObjects 1 }
sledLoopback      OBJECT IDENTIFIER ::= { sledMibObjects 2 }
sledPktGen        OBJECT IDENTIFIER ::= { sledMibObjects 3 }

--
-- The following group describes the objects that apply to
-- both loopback and packet generator SLED functionality
-- 

sledGlobalEnable OBJECT-TYPE
    SYNTAX      TruthValue 
    MAX-ACCESS  read-write
    STATUS      current
    DESCRIPTION
            "This object allows the SLED functionality to be 
            enabled/disabled. This object may only be updated prior to
            device registration. If the device has completed
            registration, any attempt to update the value of this
            object returns 'notWritable'. Prior to registration, if the
            value of this object is set to 'true', the SLED
            functionality is enabled and access to this MIB is allowed.
            Prior to registration, if the value of this object is set
            to 'false', the SLED functionality is disabled and any
            attempt to update other objects in this MIB returns
            'noAccess'."
    DEFVAL { false }
    ::= { sledGlobal 1 } 

--
-- The following group describes the loopback objects 
--

sledLoopbackInterface OBJECT-TYPE
    SYNTAX      InterfaceIndex
    MAX-ACCESS  read-write
    STATUS      current
    DESCRIPTION
            "The index of the logical CPE interface (LCI) that the SLED
            loopback function is attached to.  If the index does not
            correspond to a LCI supported by this device, 'wrongValue'
            is returned.
            Any attempt to set this object while sledLoopbackEnable is
            set to 'true' returns'notWritable'."
    ::= { sledLoopback 1 }

sledLoopbackEnable OBJECT-TYPE
    SYNTAX      TruthValue 
    MAX-ACCESS  read-write
    STATUS      current
    DESCRIPTION
            "Setting this object to 'true' enables the loopback
            function. Setting this object to 'false' disables the
            loopback function. When enabled, the eCM removes the
            Ethernet FCS/CRC32 from the original packets. All Ethernet
            packets received by the SLED from the LCI are then processed
            as follows: 

            1. If the received Ethernet packet is greater than 1472
              octets, the Ethernet packet is split into two fragments,
              the first consisting of the first 1472 octets of the
              Ethernet packet and the second containing the remaining
              octets, resulting in two payloads that are processed as
              described below. If the received Ethernet packet is less
              than or equal to 1472 octets, the entire packet will be
              processed as a single payload. 
            2. For each payload generated in step 1, the payload is 
              appended to the contents of sledLoopbackPktHdr.
            3. The mutable fields within sledLoopbackPktHdr MUST be 
              recomputed. The mutable fields are IP Header Checksum, IP
              Total Length, UDP Checksum, and UDP Length.
            4. If the Ethernet packet was fragmented in step 1, the 
              appropriate IP header fields (Flags and Fragment Offset) 
              are updated to indicate IP fragmentation These IP
              fragmentation header values will differ depending on
              if this is the first or second fragment being processed.
            5. The Ethernet FCS is computed and appended.
            6. The resulting Ethernet packet is transmitted to the
              LCI."
    DEFVAL { false }
    ::= { sledLoopback 2 }

sledLoopbackPktHdr OBJECT-TYPE
    SYNTAX      OCTET STRING (SIZE(42)) 
    MAX-ACCESS  read-write
    STATUS      current
    DESCRIPTION
            "A properly formatted Ethernet(DIX)+IP+UDP headers for use
            in SLED loopback processing as described in
            sledLoopbackEnable. The object value contains mutable
            fields that are recomputed: the IP Header Checksum,
            IP Total Length, UDP Length, and UDP Checksum. Any attempt
            to set this object while sledLoopbackEnable is set to
            'true' returns 'notWritable'."
    ::= { sledLoopback 3 }
--
-- The following group describes the packet generation objects 
--

sledPktGenInterface OBJECT-TYPE
    SYNTAX      InterfaceIndex
    MAX-ACCESS  read-write
    STATUS      current
    DESCRIPTION
            "The index of the logical CPE interface (LCI) that the SLED
            packet generation function is attached to.  If the index
            does not correspond to a LCI supported by the device,
            'wrongValue' is returned. Any attempt to set this object
            while sledPktGenTrigger is set to 'start' returns
            'notWritable'."
    ::= { sledPktGen 1 }

sledPktGenPayload OBJECT-TYPE
    SYNTAX      OCTET STRING (SIZE(64..1518)) 
    MAX-ACCESS  read-write
    STATUS      current
    DESCRIPTION
            "The properly formatted Ethernet packet payload to be
            generated. Any attempt to set this object while
            sledPktGenTrigger  is set to 'start' returns
            'notWritable'."
    ::= { sledPktGen 2 }

sledPktGenRate OBJECT-TYPE
    SYNTAX      Unsigned32 
    MAX-ACCESS  read-write
    STATUS      current
    DESCRIPTION
            "The packet rate (in packets per second) that the SLED is
            to transmit the packet specified in the sledPktGenPayload.
            Any attempt to set this object while sledPktGenTrigger is
            set to 'start' returns 'notWritable'."
    DEFVAL { 10 }
    ::= { sledPktGen 3 }

sledPktGenNumPkts OBJECT-TYPE
    SYNTAX      Unsigned32 
    MAX-ACCESS  read-write
    STATUS      current
    DESCRIPTION
            "Number of packets to be generated at the rate specified by
            sledPktGenRate. Any attempt to set this object while
            sledPktGenTrigger  has been set to 'start' will return
            'notWritable'."
    DEFVAL { 1 }
    ::= { sledPktGen 4 }

sledPktGenTrigger OBJECT-TYPE
    SYNTAX      INTEGER {
       start(1),
       stop(2)
    } 
    MAX-ACCESS  read-write
    STATUS      current
    DESCRIPTION
            "This object controls the packet generation.  Setting this
            object to 'start' causes the packet generation to begin.
            Reading this object will return 'start' if a packet
            generation is in progress, otherwise it will return 'stop'.
            Setting this object to 'stop' while packet generation is in
            progress aborts the packet generation.  Setting this object
            to 'start' while packet generation is in progress,
            'wrongValue' is returned."
    DEFVAL { stop }
    ::= { sledPktGen 5 }

sledPktGenLastTrigger OBJECT-TYPE
    SYNTAX      TimeStamp 
    MAX-ACCESS  read-only
    STATUS      current
    DESCRIPTION
            "Value of sysUptime when the  packet generation was
            last triggered."
    ::= { sledPktGen 6 }

-- Conformance information *******************************************

sledMibCompliances  OBJECT IDENTIFIER ::= { sledMibConformance 1 }
sledMibGroups       OBJECT IDENTIFIER ::= { sledMibConformance 2 }

-- Compliance statements

sledMibCompliance MODULE-COMPLIANCE
    STATUS      current
    DESCRIPTION
            "The compliance statement for SLED."
    MODULE

-- unconditionally mandatory groups

    MANDATORY-GROUPS {
            sledMibBaseGroup
    }

    ::= { sledMibCompliances 1 }


sledMibBaseGroup OBJECT-GROUP
    OBJECTS {
           sledGlobalEnable,
           sledLoopbackInterface,
           sledLoopbackEnable,
           sledLoopbackPktHdr,
           sledPktGenInterface,
           sledPktGenPayload,
           sledPktGenRate,
           sledPktGenNumPkts, 
           sledPktGenTrigger,  
           sledPktGenLastTrigger 
    }
    STATUS      current
    DESCRIPTION
            "Group of object in SLED MIB."
    ::= { sledMibGroups 1 } 

END
